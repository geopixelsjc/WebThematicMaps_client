FME workspace shape2GeoJson.fmw

Parameters:
- SourceDataset_SHAPE = $(FME_MF_DIR)35MUE250GC_SIR.shp   # Source Esri Shape File(s)
- DestDataset_SHAPE = C:\Dados\Municipios2013sp   # Destination Esri Shape Folder
- DestDataset_GEOJSON = $(FME_MF_DIR)sp.geojson   # Destination GeoJSON File

Readers:
- SHAPE_1: SHAPE from $(SourceDataset_SHAPE) in SRG-SA/2000.LL

Writers:
- SHAPE_2: SHAPE to $(DestDataset_SHAPE) in SRG-SA/2000.LL
- GEOJSON_1: GEOJSON to $(DestDataset_GEOJSON) in SRG-SA/2000.LL

35MUE250GC_SIR (reader SHAPE_1)
    attributes: NM_MUNICIP char(60), CD_GEOCMU char(7)
    -> AttributeEncoder
AttributeEncoder
    ATTRLIST = NM_MUNICIP
    TREAT_AS_BYTES = Use Bytes
    ATTRCHOICE = Selected Attributes
    DEST_ENCODING = utf-8
    -> Generalizer
Generalizer
    ANGLE = 110
    ALG_TEXT = Deveau (Generalize)
    NUMWEDGES = 1
    TOLERANCE = 0.01
    PRESERVE = Yes
    -> sp (writer SHAPE_2)
    -> sp (writer GEOJSON_1)
sp (writer SHAPE_2)
    attributes: NM_MUNICIP char(60), CD_GEOCMU char(7)
sp (writer GEOJSON_1)
    attributes: NM_MUNICIP string, CD_GEOCMU string
JSONFormatter
    REMOVE_EMPTY_OBJECTS_AND_ARRAYS = No
    OUTPUT_ATTR = _formatted
    OUTPUT_ENCODING = UTF-8
    INDENT_STYLE = 3 spaces
    FORMAT = Pretty Print
    REMOVE_NULLS = No
    JSON_ATTR = CD_GEOCMU
    REMOVE_EMPTY_STRINGS = No
