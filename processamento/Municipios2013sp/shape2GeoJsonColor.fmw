FME workspace shape2GeoJsonColor.fmw

Parameters:
- DestDataset_SHAPE = C:\Dados\Municipios2013sp   # Destination Esri Shape Folder
- DestDataset_GEOJSON = $(FME_MF_DIR)sp.geojson   # Destination GeoJSON File
- SourceDataset_SHAPE_2 = $(FME_MF_DIR)sp.shp   # Source Esri Shape File(s)

Readers:
- SHAPE_3: SHAPE from $(SourceDataset_SHAPE_2)

Writers:
- SHAPE_2: SHAPE to $(DestDataset_SHAPE) in SRG-SA/2000.LL
- GEOJSON_1: GEOJSON to $(DestDataset_GEOJSON) in SRG-SA/2000.LL

sp (reader SHAPE_3)
    attributes: NM_MUNICIP char(60), CD_GEOCMU char(7)
    -> AreaCalculator
AreaCalculator
    AREA_TYPE = Plane Area
    AREA_ATTR = value
    MULT = 1
    -> AttributeRangeMapper
AttributeRangeMapper
    IN_ATTR = value
    LUT = 0,0.058666,ff0000,0.058667,0.11733,00ff00,0.11733,0.19,0000ff,,,
    OUT_ATTR = colour
    -> sp_color (writer SHAPE_2)
    -> sp_color (writer GEOJSON_1)
sp_color (writer SHAPE_2)
    attributes: NM_MUNICIP char(60), CD_GEOCMU char(7), VALUE number(10,7), COLOUR char(6)
sp_color (writer GEOJSON_1)
    attributes: NM_MUNICIP string, CD_GEOCMU string, VALUE float, COLOUR string
